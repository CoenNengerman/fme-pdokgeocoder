FME workspace Example.fmw

Parameters:
- SourceDataset_CSV = $(FME_MF_DIR)data/lrkp_sample.csv   # Source CSV (CommaSeparatedValue) File(s)
- DestDataset_SPATIALITE = $(FME_MF_DIR)data/lrkp_sample.sl3   # Destination SpatiaLite Database File

Readers:
- CSV_1: CSV from $(SourceDataset_CSV)

Writers:
- SPATIALITE_1: SPATIALITE to $(DestDataset_SPATIALITE) in EPSG:28992

CSV (reader CSV_1)
    attributes: lrk_id char(1), type_oko char(4), actuele_naam_oko char(49), aantal_kindplaatsen number(3,0), status char(14), inschrijfdatum char(11), uitschrijfdatum char(11), opvanglocatie_adres char(35), opvanglocatie_postcode char(7), opvanglocatie_woonplaats char(20), naam_houder char(50), kvk_nummer_houder number(9,0), rechtsvorm_houder char(12), houder_adres char(32), houder_postcode char(7), houder_woonplaats char(22), houder_buitenland char(1), correspondentie_adres char(26), correspondentie_postcode char(7), correspondentie_woonplaats char(16), correspondentie_buitenland char(1), contact_persoon char(30), contact_telefoon char(14), contact_emailadres char(34), contact_website char(37), cbs_code number(5,0), verantwoordelijke_gemeente char(18), gastouderbureau_1 char(1), gastouderbureau_2 char(1), gastouderbureau_3 char(1),
      gastouderbureau_4 char(1), gastouderbureau_5 char(1), gastouderbureau_6 char(1), gastouderbureau_7 char(1), gastouderbureau_8 char(1), gastouderbureau_9 char(1), gastouderbureau_10 char(1)
    -> PdokGeocoder
Note: Address
PdokGeocoder
    FullAddress = @Value(opvanglocatie_adres),@Value(opvanglocatie_woonplaats)
    MapsAPI = http://geodata.nationaalgeoregister.nl
    GeocodeFormat = Freeform
    Geocoded -> lrkp (writer SPATIALITE_1)
    Not_Geocoded -> PdokGeocoder_2
Note: Postal code
PdokGeocoder_2
    FullAddress = @Value(opvanglocatie_postcode)
    MapsAPI = http://geodata.nationaalgeoregister.nl
    GeocodeFormat = Freeform
    Geocoded -> lrkp (writer SPATIALITE_1)
lrkp (writer SPATIALITE_1)
    attributes: lrk_id string(1), type_oko string(4), actuele_naam_oko string(49), aantal_kindplaatsen real(3,0), status string(14), inschrijfdatum string(11), uitschrijfdatum string(11), opvanglocatie_adres string(35), opvanglocatie_postcode string(7), opvanglocatie_woonplaats string(20), naam_houder string(50), kvk_nummer_houder real(9,0), rechtsvorm_houder string(12), houder_adres string(32), houder_postcode string(7), houder_woonplaats string(22), houder_buitenland string(1), correspondentie_adres string(26), correspondentie_postcode string(7), correspondentie_woonplaats string(16), correspondentie_buitenland string(1), contact_persoon string(30), contact_telefoon string(14), contact_emailadres string(34), contact_website string(37), cbs_code real(5,0), verantwoordelijke_gemeente string(18), gastouderbureau_1 string(1), gastouderbureau_2 string(1), gastouderbureau_3 string(1),
      gastouderbureau_4 string(1), gastouderbureau_5 string(1), gastouderbureau_6 string(1), gastouderbureau_7 string(1), gastouderbureau_8 string(1), gastouderbureau_9 string(1), gastouderbureau_10 string(1)

FME custom transformer PdokGeocoder
This transformer uses the OpenLS pdok geocoder to identify the positiion of addresses in The Netherlands.
Select whether you want to use a freeform address or discrete fields. Discrete fields are concatenated as follows, and the result is identical to manual concatenation of attribute values:
Street Address, City, State, Postal Code, Country.
Location is returned in EPSG 28992 projection (RD new).
Please note, the PDOK Geocoder has a fair use policy, so be gentle using this service.
Please Note: Usage Limits (from https://www.pdok.nl/nl/producten/pdok-services/uitleg-over-services)
Use of the PDOK OpenLS API is currently not subject to a query limit.
    Copyright (c) 2014 Safe Software Inc.
Permission is granted to anyone, free of charge, to use, modify and distribute the object code form of this transformer for any purpose, subject to the following restrictions:
1) The origin of this transformer and associated FME software must not be misrepresented.
2) This transformer may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- GeocodeFormat = Freeform   # attributes,FullAddress" Address format
- FullAddress = <Unused>   # Freeform address
- Street_Address =   # Street address
- City =
- State =
- Postal_Code =   # Postal Code
- Country =
- MapsAPI = http://geodata.nationaalgeoregister.nl   # Maps API Url

Input (input)
    -> AttributeCreator_2
Geocoded (output)
Not_Geocoded (output)

Bookmark: General geocoding prep
Note: Add all necessary / attributes
AttributeCreator_2
    ATTR_LIST = GG_StrAdd,$(Street_Address),GG_City,$(City),GG_State,$(State),GG_PCode,$(Postal_Code),GG_Country,$(Country)
    -> AttributeCreator_3
Note: Select appropriate full address / depending on format
AttributeCreator_3
    ATTR_LIST = GG_FullAddress,"FME_CONDITIONAL:DEFAULT_VALUE'@Value(GG_StrAdd),@Value(GG_City),@Value(GG_State),@Value(GG_PCode),@Value(GG_Country)'BOOL_OP;OR;COMPOSITE_TEST;<Unused>;TEST $(GeocodeFormat) = Freeform'$(FullAddress)'FME_NUM_CONDITIONS2___"
    -> PythonCaller_2
Note: Make sure address / is URL encoded
PythonCaller_2
    PYTHONSOURCE:
      import fmeobjects,urllib

      # Template Function interface:
      def processFeature(feature):

          # Make sure all address attributes are URL safe
          streetaddress = urllib.quote_plus(str(feature.getAttribute("GG_StrAdd")))
          feature.setAttribute("GG_StrAdd",streetaddress)
          streetaddress = urllib.quote_plus(str(feature.getAttribute("GG_City")))
          feature.setAttribute("GG_City",streetaddress)
          streetaddress = urllib.quote_plus(str(feature.getAttribute("GG_State")))
          feature.setAttribute("GG_State",streetaddress)
          streetaddress = urllib.quote_plus(str(feature.getAttribute("GG_PCode")))
          feature.setAttribute("GG_PCode",streetaddress)
          streetaddress = urllib.quote_plus(str(feature.getAttribute("GG_Country")))
          feature.setAttribute("GG_Country",streetaddress)
    PYTHONSYMBOL = processFeature
    -> BuildURL_2
Note: Build URL part needed for / creating Digital Signature
BuildURL_2: StringConcatenator
    PARM_LINE = /geocoder/Geocoder?zoekterm=@Value(GG_FullAddress)
    VAL_ATTR = URLtoSign
    -> BuildURL_4
Note: Build Complete / URL for request
BuildURL_4: StringConcatenator
    PARM_LINE = $(MapsAPI)@Value(URLtoSign)
    VAL_ATTR = pdokGeocodeURL
    -> PdokGeocode

Bookmark: Geocode
PdokGeocode: HTTPFetcher
    TARGET_URL = @Value(pdokGeocodeURL)
    STATUS_CODE_ATTR = _http_status_code
    SAVE_FILE = No
    PROXY_AUTH_METHOD = Basic
    RESPONSE_HEADER_LIST_ATTR = _headers
    ERROR_ATTR = _error
    USE_COOKIES = No
    AUTH_METHOD = Basic
    TARGET_ATTR = geocode_xml
    <REJECTED> -> AttributeRemover_2
    -> XMLFlattener

Bookmark: Decode PDOK Geocode
Note: Flatten The returned XML / and create attributes
XMLFlattener
    ATTRIBUTE_XML = geocode_xml
    XML_SOURCE_TYPE = Attribute with XML document
    EMBEDDED_EXPRESSIONS = GeocodeResponseList
    FLATTEN_OPTIONS = <structure separator="." map-empty-elements="yes" matched-prefix="attributes" matched-attributes="yes" cardinality="+{?}" structure-prefix="" child-position-attribute="" except-expression="" ui-mode="basic" matched-ancestor-attributes=""/>
    -> BulkAttributeRenamer_3
Note: Unwrap the results group / from the first group inside it
BulkAttributeRenamer_3
    REPLACE_STR = GeocodeResponseList{0}.
    ATTRCHOICE = All Attributes
    PATTERN_ACTION_DISP = Remove Prefix String
    CASE_DISP = yes
    -> BulkAttributeRenamer
BulkAttributeRenamer
    REPLACE_STR = GeocodedAddress.
    ATTRCHOICE = All Attributes
    PATTERN_ACTION_DISP = Remove Prefix String
    CASE_DISP = yes
    -> BulkAttributeRenamer_2
Note: Remove the / "GeocodedAddress." prefix
BulkAttributeRenamer_2
    REPLACE_STR = GeocodedAddress{0}.
    ATTRCHOICE = All Attributes
    PATTERN_ACTION_DISP = Remove Prefix String
    CASE_DISP = yes
    -> AttributeExposer
Note: Expose attributes
AttributeExposer
    ATTR_LIST = Address.countryCode,Address.Place{1},Address.Place{1}.type,Address.Place{2},Address.PostalCode,Address.StreetAddress.Street,Point.pos,GeocodeResponseList.numberOfGeocodedAddresses
    -> AttributeSplitter
AttributeSplitter
    LIST_NAME = _pos
    ATTR_NAME = Point.pos
    DELIMITER = " "
    TRIM_OPTION = Both
    DROP_EMPTY_PARTS = No
    -> 2DPointReplacer
Note: Replace the feature with a / point at returned XY
2DPointReplacer
    XVALATTR = @Value(_pos{0})
    YVALATTR = @Value(_pos{1})
    POINT -> AttributeRemover
Note: Remote Extra attributes
AttributeRemover
    LIST_ATTRS = Address.Place{} _headers{}.value _headers{}.name _pos{} Address.Place{}.type _headers{}
    REMOVE_ATTRS = pdokGeocodeURL,_http_status_code,geocode_xml,Address.countryCode,Address.PostalCode,Address.StreetAddress.Street,Point.pos
    -> TestFilter
Note: Check whether Geocoding / has been successful
TestFilter
    TEST_LIST = BOOL_OP,OR,COMPOSITE_TEST,<Unused>,TEST_CLAUSE,"TEST @Value(GeocodeResponseList.numberOfGeocodedAddresses) > 0",Geocoded
    DEFAULT_VALUE = Not Geocoded
    Geocoded -> CoordinateSystemSetter
    Not Geocoded -> Not_Geocoded (output)
Note: set coordinate system
CoordinateSystemSetter
    COORDSYS = EPSG:28992
    -> Geocoded (output)

Bookmark: PDOK Geocoder
Note: Invoke PDOK Geocoder
Note: HTTP Call has failed. Check the _http_status_code and _error attributes on the feature
Note: Remove the / "GeocodedAddress." prefix
AttributeRemover_2
    LIST_ATTRS = _headers{}.value _headers{}.name _headers{}
    REMOVE_ATTRS = googleGeocodeURL,GG_StrAdd,GG_City,GG_State,GG_PCode,GG_Country,cryptokey,encodedsignature,URLtoSign,geocode_json
    -> Not_Geocoded (output)
